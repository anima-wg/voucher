module iana-voucher-assertion-type {
  namespace "urn:ietf:params:xml:ns:yang:"
    + "iana-voucher-assertion-type";
  prefix ianavat;

  organization
    "IANA";
  contact
    "Internet Assigned Numbers Authority
     Postal: ICANN
             12025 Waterfront Drive, Suite 300
             Los Angeles, CA 90094-2536
             United States of America
     Tel:    +1 310 301 5800
     <mailto:iana@iana.org>";
  description
    "This YANG module defines a YANG enumeration type for
     IANA-registered voucher assertion type. This YANG
     module is maintained by IANA and reflects the
     'voucher assertion types' registry.
     The lastest revision of this YANG module can be
     obtained from the IANA web site.  Request for new
     enumerations should be made to IANA via email(iana@iana.org).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2018 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXX; see the
     RFC itself for full legal notices.";

  revision YYYY-MM-DD {
    description
      "Initial version";
    reference "RFC XXXX: Voucher Artifact for" +
      "Bootstrapping Protocols";
  }

  typedef voucher-assertion {
    type enumeration {
      enum verified {
        value 0;
        description
          "Indicates that the ownership has been positively verified
           by the MASA (e.g., through sales channel integration).";
      }
      enum logged {
        value 1;
        description
          "Indicates that the voucher has been issued after
           minimal verification of ownership or control.  The
           issuance has been logged for detection of
           potential security issues (e.g., recipients of
           vouchers might verify for themselves that unexpected
           vouchers are not in the log).  This is similar to
           unsecured trust-on-first-use principles but with the
           logging providing a basis for detecting unexpected
           events.";
      }
      enum proximity {
        value 2;
        description
          "Indicates that the voucher has been issued after
           the MASA verified a proximity proof provided by the
           device and target domain.  The issuance has been logged
           for detection of potential security issues.  This is
           stronger than just logging, because it requires some
           verification that the pledge and owner are
           in communication but is still dependent on analysis of
           the logs to detect unexpected events.";
      }
      enum agent-proximity {
        value 3;
        description
          "Indicates that the voucher has been issued after the
           MASA...support of asynchronous enrollment in BRSKI";
      }
    }
    description "Indicates what kind of ownership is being asserted by voucher";
  }
}
