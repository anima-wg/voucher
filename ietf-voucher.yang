module ietf-voucher {
  yang-version 1.1;
  namespace "urn:ietf:params:xml:ns:yang:ietf-voucher";
  prefix vch;

  import ietf-yang-types {
    prefix yang;
    reference "RFC 9911: Common YANG Data Types";
  }

  import ietf-inet-types {
    prefix ietf;
    reference "RFC 9911: Common YANG Data Types";
  }

  import ietf-yang-structure-ext {
    prefix sx;
    reference "RFC 8791: YANG Data Structure Extensions";
  }

  organization
    "IETF ANIMA Working Group";
  contact
   "WG Web:   <https://datatracker.ietf.org/wg/anima/>
    WG List:  <mailto:anima@ietf.org>
    Author:   Kent Watsen
              <mailto:kent+ietf@watsen.net>
    Author:   Michael Richardson
              <mailto:mcr+ietf@sandelman.ca>
    Author:   Toerless Eckert
              <mailto:tte@cs.fau.de>
    Author:   Qiufang Ma
              <mailto:maqiufang1@huawei.com>
    Author:   Esko Dijk
              <mailto:esko.dijk@iotconsultancy.nl>";

  description
    "This module defines the format for a Voucher, which is
     produced by a Pledge's manufacturer or delegate (MASA)
     to securely assign a Pledge to an 'owner', so that the
     Pledge may establish a secure connection to the owner's
     network infrastructure.

     Copyright (c) 2023-2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

// RFCEDITOR: please replace XXXX in this entire code fragment
// with the RFC number assigned and remove this notice.
// Please also update references in the description {{}} to the
// RFC numbers for the documents.

  revision YYYY-MM-DD {
    description
      "Updates and additions described by RFC XXXX,
      includes mechanism for constrained BRSKI
      {{I-D.ietf-anima-constrained-voucher}},
      Pledge in Responder Mode {{I-D.ietf-anima-brski-prm}},
      and BRSKI-CLOUD {{I-D.ietf-anima-brski-cloud}}";
    reference
      "RFC XXXX: A Voucher Artifact for Onboarding Protocols";
  }

  revision 2018-05-09 {
    description
      "Initial version";
    reference
      "RFC 8366: Voucher Profile for Bootstrapping Protocols";
  }

  grouping voucher-artifact {
    description
      "Grouping to allow reuse/extensions in future work.";

      leaf created-on {
        type yang:date-and-time;
        description
          "A value indicating the date this Voucher was created.
           This node is primarily for human consumption and auditing.
           Future work MAY create verification requirements based on
           this node.";
      }

      leaf-list extensions {
        type union {
            type uint64;  // when serialized to CBOR with SID
            type string;  // when serialized to CBOR or JSON
        }
        description
          "A list of extension names that are used in this Voucher
           file.  Typically, names are registered with the IANA.
           Standard extensions are described in an RFC, while vendor
           proprietary ones are not.";
      }

      leaf manufacturer-proprietary {
        type binary;
        description
          "In CBOR serialization, this is a CBOR bstr containing any
           valid CBOR that the manufacturer wishes to share with its
           Pledge.  In JSON serializations, this contains additional
           JSON instead, and it is base64URL encoded.

           Since a Voucher could be logged or stored by a Registrar
           or another intermediate, this Attribute MUST NOT contain
           any data that requires confidentiality.";
      }

      leaf assertion {
        type enumeration {
          enum verified {
            value 0;
            description
              "Indicates that the ownership has been positively
               verified by the MASA (e.g., through sales channel
               integration).";
          }
          enum logged {
            value 1;
            description
              "Indicates that the Voucher has been issued after
               minimal verification of ownership or control.  The
               issuance has been logged for detection of
               potential security issues (e.g., recipients of
               Vouchers might verify for themselves that unexpected
               Vouchers are not in the log).  This is similar to
               unsecured trust-on-first-use principles but with the
               logging providing a basis for detecting unexpected
               events.";
          }
          enum proximity {
            value 2;
            description
              "Indicates that the Voucher has been issued after
               the MASA verified a proximity proof provided by the
               device and target domain.  The issuance has been
               logged for detection of potential security issues.";
          }
          enum agent-proximity {
            value 3;
            description
              "Mostly identical to proximity, but
              indicates that the Voucher has been issued
              after the MASA has verified a statement that
              a Registrar agent has made contact with the device.";
          }
        }
        description
          "The assertion is a statement from the MASA regarding how
           the owner was verified.  This statement enables Pledges
           to support more detailed policy checks.  Pledges MUST
           ensure that the assertion provided is acceptable, per
           local policy, before processing the Voucher.";
      }
      leaf serial-number {
        type string;
        mandatory true;
        description
          "The serial-number of the hardware.  When processing a
           Voucher, a Pledge MUST ensure that its serial-number
           matches this value.  If no match occurs, then the
           Pledge MUST NOT process this Voucher.";
      }
      leaf idevid-issuer {
        type binary;
        description
          "The Authority Key Identifier OCTET STRING (as defined in
           Section 4.2.1.1 of RFC 5280) from the Pledge's IDevID
           certificate.  In the Voucher, it is optional
           as some manufacturers know that all serial-numbers
           are unique within the scope of a MASA. In the Voucher
           Request, whether it is mandatory or optional depends on
           which protocol is used, such as RFC8995 and variations.
           When processing a Voucher, a Pledge MUST ensure that its
           IDevID Authority Key Identifier matches this value. If no
           match occurs, then the Pledge MUST NOT process this
           Voucher.
           When issuing a Voucher, the MASA MUST ensure that this
           field is populated for serial-numbers that are not
           otherwise unique within the scope of the MASA.";
      }

      // The MASA typically includes only one of the below
      // pinned-domain-* Attributes in a Voucher.
      leaf pinned-domain-cert {
        type binary;
        description
         "An X.509 v3 certificate structure, as specified by
          RFC 5280, using Distinguished Encoding Rules (DER)
          encoding, as defined in [ITU-T.X690].

          This certificate is used by a Pledge to trust a Public Key
          Infrastructure in order to verify a domain certificate
          supplied to the Pledge separately by the onboarding
          protocol.  The domain certificate MUST have this
          certificate somewhere in its chain of certificates.
          This certificate MAY be an end-entity certificate,
          including a self-signed entity.";
        reference
          "RFC 5280:
           Internet X.509 Public Key Infrastructure Certificate
           and Certificate Revocation List (CRL) Profile.
           ITU-T.X690:
           Information technology - ASN.1 encoding rules:
           Specification of Basic Encoding Rules (BER),
           Canonical Encoding Rules (CER) and Distinguished
           Encoding Rules (DER).";
      }
      leaf pinned-domain-pubk {
        type binary;
        description
          "The pinned-domain-pubk may replace the
           pinned-domain-cert in constrained uses of
           the Voucher. The pinned-domain-pubk
           is the Raw Public Key of the Registrar.
           This field is encoded as a Subject Public Key Info block
           as specified in RFC7250, in section 3.";
      }
      leaf pinned-domain-pubk-sha256 {
        type binary;
        description
          "The pinned-domain-pubk-sha256 is a second
           alternative to pinned-domain-cert.  In many cases the
           public key of the domain has already been transmitted
           during the key agreement process, and it is wasteful
           to transmit the public key another two times.
           The use of a hash of public key info, at 32-bytes for
           sha256 is a significant savings compared to an RSA
           public key, but is only a minor savings compared to
           a 256-bit ECDSA public key.
           Algorithm agility is provided by extensions to this
           specification which can define a new leaf for another
           hash type.";
      }
      // End of pinned-domain-* Attributes block

      leaf domain-cert-revocation-checks {
        type boolean;
        description
          "A processing instruction to the Pledge that it MUST (true)
           or MUST NOT (false) verify the revocation status for the
           pinned domain certificate.  If this field is not set, then
           normal PKIX behavior applies to validation of the domain
           certificate.";
      }
      leaf last-renewal-date {
        type yang:date-and-time;
        must '../expires-on';
        description
          "The date that the MASA projects to be the last date
           it will renew a Voucher on. This field is merely
           informative; it is not processed by Pledges.

           Circumstances may occur after a Voucher is generated that
           may alter a Voucher's validity period.  For instance,
           a vendor may associate validity periods with support
           contracts, which may be terminated or extended
           over time.";
      }

      // The MASA MUST NOT include both of the below
      // Attributes expires-on and nonce in a Voucher.
      leaf expires-on {
        type yang:date-and-time;
        description
          "A value indicating when this Voucher expires.  The node is
           optional as not all Pledges support expirations, such as
           Pledges lacking a reliable clock.

           If this field exists, then the Pledges MUST ensure that
           the expires-on time has not yet passed. A Pledge without
           an accurate clock cannot meet this requirement.

           The expires-on value MUST NOT exceed the expiration date
           of any of the listed 'pinned-domain-cert' certificates.

           A MASA that includes this Attribute MUST NOT include the
           'nonce' Attribute.";
      }
      leaf nonce {
        type binary {
          length "8..32";
        }
        description
          "A value that can be used by a Pledge in some onboarding
           protocols to enable anti-replay protection.  This node is
           optional because it is not used by all onboarding
           protocols.

           When present, the Pledge MUST compare the provided nonce
           value with another value that the Pledge randomly
           generated and sent to a bootstrap server in an earlier
           onboarding message.  If the value is present, but
           the values do not match, then the Pledge MUST NOT process
           this Voucher.

           A nonce value MUST be a cryptographically strong random
           value as detailed in RFC 4086.

           A MASA that includes this Attribute MUST NOT include the
           'expires-on' Attribute.";
      }
      // End of expires-on / nonce Attributes block

      leaf est-domain {
        type ietf:uri;
        description
          "The est-domain is a URL from which the Pledge should
           continue doing enrollment rather than with the
           cloud Registrar.
           The pinned-domain-cert contains a trust-anchor
           which is to be used to authenticate the server
           found at this URI.";
      }
      leaf additional-configuration-url {
        type ietf:uri;
        description
          "The additional-configuration Attribute contains a
           URL to which the Pledge can retrieve additional
           configuration information.
           The contents of this URL are manufacturer specific.
           This is intended to do things like configure
           a VoIP phone to point to the correct hosted
           PBX, for example.

           The URL MUST NOT contain any data (such as authen-
           tication tokens) that requires confidentiality.";
      }
  }

  // Top-level statement
  sx:structure voucher {
    uses voucher-artifact;
  }

}
